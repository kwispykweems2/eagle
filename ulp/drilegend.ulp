#usage "<b>Drill Legend for Eagle 4.04</b><p><p>\n"
	"This ULP add a drill legend in a board.<p>Dont forget to update the >Options>Setting>Drill<p>and sort both drill tools and drill diameters in the same ascending order as the drill legend.<p>\n"
        "You could also generate the drill configuration for the CamProcessor.<p><p>\n"
      "<author>Author: c.bohrer@m6net.fr</author>"

/****************************************************
 * DRILEGEND 2.01    for Eagle 4.04    (12/04/2002) *
 * By Christian BOHRER   (PCB Designer)             *
 * c.bohrer@m6net.fr                                *
 ****************************************************
 * THIS PROGRAM IS PROVIDED "AS IS" WITHOUT WARRANTY FOR POSSIBLE DAMAGE */

 /************** DEFAULT SETTINGS ***********************/

int SymbolLayer 	= 44;
int SymbolSize 		= 70; /*Symbol diameter*/
int SymbolWidth		= 4; /*Symbol wire width*/

string TextFont[]	= {"Vector", "Proportional", "fixed"};
int TextSize 		= 70;
int TextRatio 		= 5;
int IdxFnt		= 0; //Vector

int decMM 		= 3; /*number of decimal for milimeters*/
int decMIL 		= 0; /*number of decimal fol mils*/
int SortHoles 		= 1; /* 0= alternate, 1= mixed, 2= non-plated last*/
string TolPlated	= "0.02";
string TolNonPlated	= "0.03";
int VerticalChart	= 1; /* if 0 : Horizontal chart*/
real HighCellFactor	= 1.1; /* 1.0 minimum*/
real WideCellFactor	= 1.1; /* 1.0 minimum*/
int CellOutline		= 4;
int TitleOutline	= 4;
int TableOutline	= 8;

string LField[] = {"Symbols","Tools N°","MM","Mils","Microns","Quantity","Plated","Tolerance"};
string LTitle[]	= {"Sym","N°","MM","Mils","Mic","Qty","Plated","Tol"};
int LRank[]	= {1,2,4,3,0,5,6,0}; //Rank = from 1 to 8. ( 0 = unselect)
string Rank[]		= {"0","1","2","3","4","5","6","7","8"};
string PlatedStatus[] 	= {"NOT", "BOTH", "YES"};

int OutputDrillRack	= 0;
string DrillRackFile	= "DRILLRACK.DRL"; /* drill rack file name */
enum { unitMM, unitINCH };
int Unit 		= unitMM; /* set this to the desired unit! */

int OutputUserCfg	= 1;
int InputUserCfg 	= 1;
string UserCfgFile	= "DRILEGEND.CFG"; /* drill legend user config */
int AbsoluteLibPath	= 1;
int  i, j, k, Dcnt = 0, Lcnt = 1, nlines, LayerSel;
int index[], idx[], Drills[], Pcnt[], Hcnt[], Ptype[], Htype[];
string ScrName, ProjectPath, UserSettings[], LList[], LayerName[];
int Lpos[], Cell[], LCell[], Hcell[], Bcell[], LayerNbr[];

int EV = EAGLE_VERSION;
int ER = EAGLE_RELEASE;


/**************ADD OR UPDATE DRILL LEGEND***********************/

int replace = 0;
int rename  = 0;
string lay;
int laycnt = 0;

board(B) {
 B.elements(E) {
  if(E.name == "DRILEGEND"){
   replace = 1;
  }
 }
 ScrName = filesetext(B.name, "_DL.SCR");
 ProjectPath = filedir(B.name);

 B.layers(L) {
  if(L.used == 1) {
   sprintf(lay,"%d  %s", L.number, L.name);
   LayerName[laycnt] = lay;
   LayerNbr[laycnt] = L.number;
   laycnt++;
  }
 }
}

string LbrPath;
string UlpLbrPath;
if(AbsoluteLibPath == 1) {
 sprintf(LbrPath,"'%sdrilegend.lbr'",ProjectPath); //With '' for path in script command
 //Script command dont work without '' if the path contain a space like 'program Files'
 sprintf(UlpLbrPath,"%sdrilegend.lbr",ProjectPath); //Without '' for path in fileglob
}
else {
 LbrPath = "./drilegend.lbr";
 UlpLbrPath = "./drilegend.lbr";
}
string ok[];
rename = fileglob(ok, UlpLbrPath); //Rename package if lbr exist

int CreateCfgFile = 0;
string CfgPath;
sprintf(CfgPath,"%s\%s",ProjectPath,UserCfgFile);
string cfg[];
CreateCfgFile = fileglob(cfg, CfgPath);

/*********** SAVE USER'S SETTINGS *************************/

void OutputUserCfgFile() {
 output(CfgPath) {
  printf("InputUserCfg = %d\n", InputUserCfg);
  printf("SymbolLayer = %d\n", SymbolLayer);
  printf("SymbolSize = %d\n", SymbolSize);
  printf("SymbolWidth = %d\n", SymbolWidth);

  printf("TextSize = %d\n", TextSize);
  printf("TextRatio = %d\n", TextRatio);
  printf("IdxFnt = %d\n", IdxFnt);

  printf("decMM = %d\n", decMM);
  printf("decMIL = %d\n", decMIL);
  printf("SortHoles = %d\n", SortHoles);
  printf("TolPlated = %s\n", TolPlated);
  printf("TolNonPlated = %s\n", TolNonPlated);
  printf("PlatedStatusNot = %s\n", PlatedStatus[0]);
  printf("PlatedStatusBoth = %s\n", PlatedStatus[1]);
  printf("PlatedStatusYes = %s\n", PlatedStatus[2]);

  printf("VerticalChart = %d\n", VerticalChart);
  printf("HighCellFactor = %-.2f\n", HighCellFactor);
  printf("WideCellFactor = %-.2f\n", WideCellFactor);
  printf("CellOutline = %d\n", CellOutline);
  printf("TitleOutline = %d\n", TitleOutline);
  printf("TableOutline = %d\n", TableOutline);

  printf("SymbTitle = %s\n", LTitle[0]);
  printf("ToolTitle = %s\n", LTitle[1]);
  printf("MMTitle = %s\n", LTitle[2]);
  printf("MilTitle = %s\n", LTitle[3]);
  printf("MicTitle = %s\n", LTitle[4]);
  printf("QtyTitle = %s\n", LTitle[5]);
  printf("TypeTitle = %s\n", LTitle[6]);
  printf("ToleTitle = %s\n", LTitle[7]);

  printf("SymbRank = %d\n", LRank[0]);
  printf("ToolRank = %d\n", LRank[1]);
  printf("MMRank = %d\n", LRank[2]);
  printf("MilRank = %d\n", LRank[3]);
  printf("MicRank = %d\n", LRank[4]);
  printf("QtyRank = %d\n", LRank[5]);
  printf("TypeRank = %d\n", LRank[6]);
  printf("ToleRank = %d\n", LRank[7]);

  printf("OutputDrillRack = %d\n", OutputDrillRack);
  printf("DrillRackFile = %s\n", DrillRackFile);
  printf("Unit = %d\n", Unit);

  printf("OutputUserCfg = %d\n", OutputUserCfg);
  printf("UserCfgFile = %s\n", UserCfgFile);
 }
}

/********* LOAD USER'S SETTINGS *********************/

string LoadSettings(string var) {
string a[], b; char c = ' ';
 for(i = 0; i < nlines; i++){
  b = UserSettings[i];
  if (strsplit(a, b, c) == 3) {
   if(var == a[0]) { return a[2];
   }
  }
 }
 return var;
}

void LoadUserCfgFile() {
  InputUserCfg = strtol(LoadSettings("InputUserCfg"));
  if(InputUserCfg == 1) {
   SymbolLayer = strtol(LoadSettings("SymbolLayer"));
   SymbolSize = strtol(LoadSettings("SymbolSize"));
   SymbolWidth = strtol(LoadSettings("SymbolWidth"));

   TextSize = strtol(LoadSettings("TextSize"));
   TextRatio = strtol(LoadSettings("TextRatio"));
   IdxFnt = strtol(LoadSettings("IdxFnt"));

   decMM = strtol(LoadSettings("decMM"));
   decMIL = strtol(LoadSettings("decMIL"));
   SortHoles = strtol(LoadSettings("SortHoles"));
   TolPlated = LoadSettings("TolPlated");
   TolNonPlated = LoadSettings("TolNonPlated");
   PlatedStatus[0] = LoadSettings("PlatedStatusNot");
   PlatedStatus[1] = LoadSettings("PlatedStatusBoth");
   PlatedStatus[2] = LoadSettings("PlatedStatusYes");

   VerticalChart = strtol(LoadSettings("VerticalChart"));
   HighCellFactor = strtod(LoadSettings("HighCellFactor"));
   WideCellFactor = strtod(LoadSettings("WideCellFactor"));
   CellOutline = strtod(LoadSettings("CellOutline"));
   TitleOutline = strtod(LoadSettings("TitleOutline"));
   TableOutline = strtod(LoadSettings("TableOutline"));

   LTitle[0] = LoadSettings("SymbTitle");
   LTitle[1] = LoadSettings("ToolTitle");
   LTitle[2] = LoadSettings("MMTitle");
   LTitle[3] = LoadSettings("MilTitle");
   LTitle[4] = LoadSettings("MicTitle");
   LTitle[5] = LoadSettings("QtyTitle");
   LTitle[6] = LoadSettings("TypeTitle");
   LTitle[7] = LoadSettings("ToleTitle");

   LRank[0] = strtol(LoadSettings("SymbRank"));
   LRank[1] = strtol(LoadSettings("ToolRank"));
   LRank[2] = strtol(LoadSettings("MMRank"));
   LRank[3] = strtol(LoadSettings("MilRank"));
   LRank[4] = strtol(LoadSettings("MicRank"));
   LRank[5] = strtol(LoadSettings("QtyRank"));
   LRank[6] = strtol(LoadSettings("TypeRank"));
   LRank[7] = strtol(LoadSettings("ToleRank"));

   OutputDrillRack = strtol(LoadSettings("OutputDrillRack"));
   DrillRackFile = LoadSettings("DrillRackFile");
   Unit = strtol(LoadSettings("Unit"));

   OutputUserCfg = strtol(LoadSettings("OutputUserCfg"));
   UserCfgFile = LoadSettings("UserCfgFile");

 }
}


if(CreateCfgFile == 0)  {OutputUserCfgFile();}
if(CreateCfgFile == 1) {
 nlines = fileread(UserSettings, CfgPath);
 LoadUserCfgFile();
}


/****************** HELP *************************/

  string HelpLegend = "<qt bgcolor=wheat><h1>Legend</h1><hr><p><font size=5 color=blue><b>Drill legend Settings</b></font><p><table><tr><td width=20></td><td><font color=red><b>Title</b></font></td></tr><tr><td></td><td>Enter here the name of your choice for the title field.</td></tr><tr><td></td><td><font color=red><b>Rank</b></font></td></tr><tr><td></td><td>Choose here a number (from 1 to 8) for the position of each field in the drill legend. 0 = unselected.</td></tr></table><p><p><font size=5 color=blue><b>Drill legend Orientation</b></font><p><table><tr><td width=20></td><td><font color=red><b>Horizontal</b></font></td></tr><tr><td></td><td>Choose this option for horizontal drill legend.</td></tr><tr><td></td><td><font color=red><b>Vertical</b></font></td></tr><tr><td></td><td>Choose this option for vertical drill legend.</td></tr></table></qt>";

   string HelpSymbols = "<qt bgcolor=wheat><h1>Symbols</h1><hr><p><font size=5 color=blue><b>Symbols Settings</b></font><p><table><tr><td width=20></td><td><font color=red><b>Symbol Layer</b></font></td></tr><tr><td></td><td>Choose in this field the layer in which you want draw this drill legend.</td></tr><tr><td></td><td><font color=red><b>Symbol Size</b></font></td></tr><tr><td></td><td>Enter in this field the symbol diameter (in mils).</td></tr><tr><td></td><td><font color=red><b>Symbol Width</b></font></td></tr><tr><td></td><td>Enter in this field the symbol line width (in mils).</td></tr></table><p><font color=darkgreen><b>Nota: </b></font>Drilegend.ulp drills symbols and Eagle drills symbols are associated with the same drill tool number in the same ascending order, so each drill tool number always is associated with the same drill symbol. But, they are not associated in the same manner with the holes diameters.<p>Drilegend.ulp sort the holes diameters (like drillcfg.ulp) in ascending order before to associate each with a drill tool number, so drill tools numbers and holes diameters are sorted together in a same increasing order. Eagle extract the holes diameters as is from the board, and give them a increasing tool number without sort before.<p>The result of each method is evidently different and that's why it's very important after each run of this ulp to open the \"Options>Settings>Drill\" and verify if it's necessary to update and sort holes diameters and tools numbers in the same ascending order like the drill legend.</qt>";

    string HelpTexts = "<qt bgcolor=wheat><h1>Texts</h1><hr><p><font size=5 color=blue><b>Texts Settings</b></font><p><table><tr><td width=20></td><td><font color=red><b>Text Font</b></font></td></tr><tr><td></td><td>Choose a text font in the list.</td></tr><tr><td></td><td><font color=red><b>Text Size</b></font></td></tr><tr><td></td><td>Enter in this field the font size (in mils).</td></tr><tr><td></td><td><font color=red><b>Text Ratio</b></font></td></tr><tr><td></td><td>Enter in this field the font ratio (in %).</td></tr></table><p><font color=darkgreen><b>Nota: </b></font>For printer output choose the font what you want but for gerber output keep VECTOR.</qt>";

    string HelpTable = "<qt bgcolor=wheat><h1>Table</h1><hr><p><font size=5 color=blue><b>Cell Margin Factor</b></font><p>Enter in theses fields a value (from 1.0 to 9.9) for increase or decrease the space between texts and border cells.<p><table><tr><td width=20></td><td><font color=red><b>Horizontal </b></font></td></tr><tr><td></td><td>Horizontal space between texts and border cells.</td></tr><tr><td></td><td><font color=red><b>Vertical</b></font></td></tr><tr><td></td><td>Vertical space between texts and border cells.</td></tr></table><p><p><font size=5 color=blue><b>Outline Width</b></font><p><table><tr><td width=20></td><td><font color=red><b>Cell</b></td></tr><tr><td></td><td>Enter in this field the outline width of a cell (in mils).</td></tr><tr><td></td><td><font color=red><b>Title</b></td></tr><tr><td></td><td>Enter in this field the outline width of the title (in mils).</td></tr><tr><td></td><td><font color=red><b>Table</b></td></tr><tr><td></td><td>Enter in this field the outline width of the table (in mils).</td></tr></table></qt>";

    string HelpHoles = "<qt bgcolor=wheat><h1>Holes</h1><hr><p><font size=5 color=blue><b>Non-Plated</b></font><p>All holes diameters (plated or not plated) are sorted in ascending mode.<p><p><table><tr><td width=20></td><td><font color=red><b>Alternate</b></font></td></tr><tr><td></td><td>For each diameter, non-plated holes are treated after plated holes but before the following diameter.</td></tr><tr><td></td><td><font color=red><b>Mixed</b></font></td></tr><tr><td></td><td>Only one diameter per column. Plated and non-plated holes with same diameter are added in the same column. In this case, plated status show: \"BOTH\".</td></tr><tr><td></td><td><font color=red><b>Last</b></font></td></tr><tr><td></td><td>All plated holes diameter are treated first, then all non-plated are treated last.</td></tr></table><p><p><font size=5 color=blue><b>Plated Status</b></font><p><table><tr><td width=20></td><td><font color=red><b>Not Plated</b></td></tr><tr><td></td><td>Enter in this field a string meaning: not plated hole. Default: \"NOT\".</td></tr><tr><td></td><td><font color=red><b>Mixed</b></td></tr><tr><td></td><td>Enter in this field a string meaning: plated and not plated use the same drill tool. Default: \"BOTH\".</td></tr><tr><td></td><td><font color=red><b>Plated</b></td></tr><tr><td></td><td>Enter in this field a string meaning: plated hole. Default: \"YES\".</td></tr></table><p><font color=darkgreen><b>Nota: </b></font>Avoid to use the same diameter for plated an non-plated holes.<p><p><font size=5 color=blue><b>Unit Precision</b></font><p>Choose here the number of unit after the decimal point.<table><tr><td width=20></td><td><font color=red><b>Mils</b></font></td></tr><tr><td></td><td>Unit of precision for mils.</td></tr><tr><td></td><td><font color=red><b>MM</b></font></td></tr><tr><td></td><td>Unit of precision for millimeters.</td></tr></table><p><p><font size=5 color=blue><b>Holes Tolerance</b></font><p><table><tr><td width=20></td><td><font color=red><b>Plated Holes</b></font></td></tr><tr><td></td><td>Enter in this field your value for plated holes tolerance.</td></tr><tr><td></td><td><font color=red><b>Non-Plated Holes</b></font></td></tr><tr><td></td><td>Enter in this field your value for non-plated holes tolerance.</td></tr></table><p><font color=darkgreen><b>Nota: </b></font>Tolerance field is String type, so you can enter anything like: 0,02 or +/- 0.03</qt>";

    string HelpOutputs = "<qt bgcolor=wheat><h1>Outputs</h1><hr><p><font size=5 color=blue><b>Drill Rack File for CAM Processor</b></font><p><table><tr><td width=20></td><td><font color=red><b>Create file</b></font></td></tr><tr><td></td><td>Click on this check button for create the drill rack file used in the cam processor. Choose the output unit: milimeters or inches.</td></tr></table></qt>";

/******** ARRAY OF 18 EAGLE DRILL SYMBOLS ********/

//4 + + + + +
//3 + + + + +
//2 + + + + +
//1 + + + + +
//0 + + + + +
//  0 1 2 3 4

string Symbol[] = {
"W 24 20,W 02 42",
"W 04 40,W 44 00",
"W 22 24 44 40 00 04 24",
"W 22 24 42 20 02 24",
"W 04 44 00 40 04",
"W 04 40 44 00 04",
"W 02 42 24 20 02",
"W 24 20 42 02 24",
"W 04 40,W 44 00,W 24 20",
"W 04 40,W 44 00,W 02 42",
"W 04 44 22 04,W 22 20",
"W 24 22 40 00 22",
"W 02 22 44 40 22",
"W 42 22 04 00 22",
"W 24 20,W 02 42,C 22 42",
"C 22 42,C 22 32,W 24 20,W 02 42",
"W 04 24 44 42 40 20 00 02 04,W 24 20,W 02 42",
"W 04 02 00 20 40 42 44 24 04,W 13 11 31 33 13,W 24 20,W 02 42",
"C 22 42,W 00 44"};

string DrawSymbol(int No, int Xs, int Ys) {
Xs = Xs - (SymbolSize/2);
Ys = Ys - (SymbolSize/2);
string a[], c[], tmps, cmd, hs;
int b = 0, d = 0, U = SymbolSize/4, sx, sy, m, p;

 b = strsplit(a, Symbol[No], ',');
 for(m=0;m<b;m++) {
  d = strsplit(c, a[m], ' ');
  if(c[0] == "W") {cmd = "Wire";}
  if(c[0] == "C") {cmd = "Circle";}
  hs=""; sprintf(hs,"%s %d",cmd,SymbolWidth); tmps += hs;
  for(p=1;p<d;p++) {
   sx = strtol(strsub(c[p],0,1)); sx = (sx*U) + Xs;
   sy = strtol(strsub(c[p],1,1)); sy = (sy*U) + Ys;
   hs=""; sprintf(hs," (%d %d)",sx,sy); tmps += hs;
  }
  hs=""; sprintf(hs,";\n"); tmps += hs;
 }
 return tmps;
}

/*****************************************************/

int CenterText(string txt, int cell, int pos)
{
	return pos + (round((cell-((TextSize* 0.85)*strlen(txt)))/2));
}

void printCell(int left, int right, int top, int bottom, int width)
{
 printf("Wire %d (%d %d) (%d %d) (%d %d);\n", width,
 left, bottom, right, bottom, right, top);
}

void DrillChartVertical(int bas)
{
 int haut;
 if(TextSize > SymbolSize*0.7) { haut = TextSize * 1.5 * HighCellFactor;}
 else { haut = SymbolSize * HighCellFactor;}
 int org =  (haut - TextSize)/2, WideMax = 0;

 for(int i = 0; i < Lcnt; ++i)
 {

  for(k = 0; k < 8; k++)
  {
   if(LRank[k] > 0)
   {
    if((k == 0) && (i > 0))
    {
     printf(DrawSymbol(strtol(LList[i]),Lpos[LRank[k]]+(LCell[k]/2), bas +(haut/2)));
    }
    else
    {
     printf("Text '%s' R0 (%d %d);\n", LList[(k*100)+i],
     CenterText(LList[(k*100)+i], LCell[k], Lpos[LRank[k]]), bas + org);
    }
    printCell(Lpos[LRank[k]], Lpos[LRank[k]] + LCell[k], haut, bas, CellOutline);
    if(i == 0) { WideMax = WideMax + LCell[k];
    }
   }
  }

  bas = bas - haut;
 }
   printCell(0, WideMax, haut, 0, TitleOutline);
   printCell(WideMax, 0, 0, haut, TitleOutline);
   printCell(0, WideMax, haut, bas + haut, TableOutline);
   printCell(WideMax, 0, bas + haut, haut, TableOutline);
}


void DrillChartHorizontal(int gauche)
{
 int bas, org, WideMax = 0;

 for(int i = 0; i < Lcnt; ++i)
 {

  for(k = 0; k < 8; k++){ //k = 8 Fields
   if(LRank[k] > 0)
   {

    bas = Bcell[LRank[k]];
    if(Cell[i] < Hcell[0])
    {
    	Cell[i] = SymbolSize * 1.3 * WideCellFactor;
    }
    org =  (Hcell[k] - TextSize)/2;

    if(bas < WideMax) { WideMax = bas;}

    if((k == 0) && (i > 0))
    { // if symbol field but not title field
     printf(DrawSymbol(strtol(LList[i]),gauche+(Cell[i]/2), bas +(Hcell[k]/2)));
     printCell(gauche, gauche + Cell[i], bas + Hcell[k], bas, CellOutline);
    }
    else
    {
     printf("Text '%s' R0 (%d %d);\n", LList[(k*100)+i],
     CenterText(LList[(k*100)+i], Cell[i], gauche), bas + org);
     printCell(gauche, gauche + Cell[i], bas + Hcell[k], bas, CellOutline);
    }
   }
  }

  gauche = gauche + Cell[i];

   printCell(0, Cell[0], 0, WideMax, TitleOutline);
   printCell( Cell[0], 0, WideMax, 0, TitleOutline);

 }
 printCell(0, gauche, 0, WideMax, TableOutline);
 printCell(gauche, 0, WideMax, 0, TableOutline);
}

void defHigh()
{ // for horizontal table
 if(TextSize > SymbolSize) { Hcell[0] = TextSize * 1.5 * HighCellFactor;}
 else
 { Hcell[0] = SymbolSize * 1.5 * HighCellFactor;}
 for(i = 1; i < 8; i++)
 {
 	Hcell[i] = TextSize * 1.5 * HighCellFactor;
 }

 int tmp[];
 for(i = 0; i < 8; i++) {
 tmp[LRank[i]] = Hcell[i];
 }

 for(i = 1; i < 9; i++) {
  Bcell[i] = Bcell[i-1] - tmp[i];
 }
}

void defPos() { //for vertical table
 if(LCell[0] < SymbolSize*1.2) { LCell[0] = SymbolSize * 1.2 * WideCellFactor;}
 int tmp[];
 for(i = 0; i < 8; i++) {
 tmp[LRank[i]] = LCell[i];
 }

 for(i = 1; i < 8; i++) {
  Lpos[i+1] = Lpos[i] + tmp[i];
 }
}


int CellLarge(string txt, int old) {
 int new = (round((TextSize * 0.1 * WideCellFactor)*strlen(txt)))*10;
 if( new > old) {return new;}
 else { return old;}
}

void TitleList() {
 for(i=0;i<8;i++){
  LList[i*100]  = LTitle[i];
  LCell[i]    	= CellLarge(LList[i*100], LCell[i]);
  Cell[0]	= CellLarge(LList[i*100], Cell[0]);
 }
}

void List(int No, int Diam, int Qty, int Type, int cnt, string Tol) {
 sprintf(LList[cnt], "%d",No);
 sprintf(LList[100+cnt], "%d",No + 1);
 if(decMM  == 0) {sprintf( LList[200+cnt], "%-.0f", round(Diam/1000)/10  );}
 if(decMM  == 1) {sprintf( LList[200+cnt], "%-.1f", round(Diam/100)/100  );}
 if(decMM  == 2) {sprintf( LList[200+cnt], "%-.2f", round(Diam/10)/1000  );}
 if(decMM  == 3) {sprintf( LList[200+cnt], "%-.3f", round(Diam)/10000    );}
 if(decMIL == 0) {sprintf(LList[300+cnt], "%-.0f", round((Diam/25.4)/10));}
 if(decMIL == 1) {sprintf(LList[300+cnt], "%-.1f", round(Diam/25.4)/10  );}
 if(decMIL == 2) {sprintf(LList[300+cnt], "%-.2f", round(Diam/2.54)/100 );}
 if(decMIL == 3) {sprintf(LList[300+cnt], "%-.3f", round(Diam/0.254)/1000 );}
 sprintf( LList[400+cnt], "%-.0f", round(Diam/10) );
 sprintf( LList[500+cnt], "%d", Qty);
 sprintf( LList[600+cnt], "%s", PlatedStatus[Type]);
 sprintf( LList[700+cnt], "%s", Tol);

 for(k=1;k<8;k++){
 LCell[k]  = CellLarge(LList[(k*100)+cnt], LCell[k]); //Vertical table
 if(LRank[k] > 0) {Cell[cnt] = CellLarge(LList[(k*100)+cnt], Cell[cnt]);}//Horizontal table
 }
}

void DrillsCapture(int Size, int Plated) {

 for(i = Dcnt; --i >= 0; ) {
  if(Drills[i] == Size) {
   if(Plated == 1) {
    Ptype[i] = 1;
    Pcnt[i]++;
    return;
   }
   if(Plated == 0) {
    Htype[i] = 0;
    Hcnt[i]++;
    return;
   }
  }
 }

  Drills[Dcnt] = Size;
  Htype[Dcnt] = 1;

  if(Plated == 1) {
   Ptype[Dcnt] = 1;
   Pcnt[Dcnt]++;
  }
  if(Plated == 0) {
   Htype[Dcnt] = 0;
   Hcnt[Dcnt]++;
  }
  Dcnt++;

}

board(B) {
  B.holes(H) DrillsCapture(H.drill, 0);
  B.signals(S) S.vias(V) DrillsCapture(V.drill, 1);
  B.elements(E)  {
    E.package.contacts(C) {
      if (C.pad) DrillsCapture(C.pad.drill, 1);
    }
    E.package.holes(H) DrillsCapture(H.drill, 0);
  }
}

sort(Dcnt, index, Drills);

void SortHolesMode(int Mode) {
 if(Mode == 0) {//ALTERNATE
  for( i = 0; i < Dcnt; i++) {
   if(Ptype[index[i]] == 1) {
    List(i, Drills[index[i]], Pcnt[index[i]], Ptype[index[i]] + 1, Lcnt, TolPlated);
    Lcnt++;
   }
   if(Htype[index[i]] == 0) {
    List(i, Drills[index[i]], Hcnt[index[i]], Htype[index[i]] + 0, Lcnt, TolNonPlated);
    Lcnt++;
   }
  }
 }

 if(Mode == 1) { //MIXED
  string tol;
  for( i = 0; i < Dcnt; i++) {
   if(Ptype[index[i]] + Htype[index[i]] == 0) {tol = TolNonPlated;}
   else {tol = TolPlated;}
   List(i, Drills[index[i]], Pcnt[index[i]] + Hcnt[index[i]], Ptype[index[i]] + Htype[index[i]], Lcnt, tol);
   Lcnt++;
  }
 }


 if(Mode == 2) {//AT END
  for( i = 0; i < Dcnt; i++) {
   if(Ptype[index[i]] == 1) {
    List(i, Drills[index[i]], Pcnt[index[i]], Ptype[index[i]] + 1, Lcnt, TolPlated);
    Lcnt++;
   }
  }
  for( i = 0; i < Dcnt; i++) {
   if(Htype[index[i]] == 0) {
    List(i, Drills[index[i]], Hcnt[index[i]], Htype[index[i]] + 0, Lcnt, TolNonPlated);
    Lcnt++;
   }
  }
 }
}


/******* DRILL RACK FOR THE CAM PROCESSOR (DRILLCFG.ULP) *******/

 string unitName[] = { "mm", "in" };
 int unitPrec[] = { 2, 3 };
 int RoundFactor = pow(10, unitPrec[Unit]);
 real Drilling[];
 int imax = 0;

 void AddDrilling(int Size)
 {
  real x;

  switch (Unit) {
    case unitMM:   x = round(u2mm(Size) * RoundFactor) / RoundFactor;
                   break;
    case unitINCH: x = round(u2inch(Size) * RoundFactor) / RoundFactor;
                   break;
  }

  for (int i = imax; --i >= 0; )
      if (Drilling[i] == x)
         return;
  Drilling[imax++] = x;
 }

void OutDrillRack() {
 board(B) {
  B.holes(H) AddDrilling(H.drill);
  B.signals(S) S.vias(V) AddDrilling(V.drill);
  B.elements(E) {
   E.package.contacts(C) {
    if (C.pad)
     AddDrilling(C.pad.drill);
   }
   E.package.holes(H) AddDrilling(H.drill);
  }
  sort(imax, Drilling);
  output(DrillRackFile) {
   for (int i = 0; i < imax; ++i)
    printf("T%02d %5.*f%s\n", i + 1, unitPrec[Unit], Drilling[i], unitName[Unit]);
  }
 }
}

/*******OUTPUT DRILL LEGEND FILE****************/

for(j = 0; j < laycnt; j++) {
 if(LayerNbr[j] == SymbolLayer) {
  LayerSel = j;}
}

void OutDriLegend() {
 output(ScrName) {
  printf("OPEN %s;\n",LbrPath);
  int ttime = time();
  string ftime;
  sprintf(ftime,"%d",ttime);
  string tfile = strsub(ftime, 2, 9);

  if(rename == 1) {
   printf("Rename drilegend.pac dl%s.pac\n",tfile);
  }
  printf("Edit drilegend.pac\n");
  printf("Display none;\n");
  printf("Display %d;\n", SymbolLayer);
  printf("Set Wire_Bend 2;\n");
  printf("Grid mil 25 1 mil;\n");

  for(j = 0; j < laycnt; j++) {
   printf("Layer %s;\n",LayerName[j]);
  }
  printf("Change layer %d;\n", SymbolLayer);
  printf("Change Size %d;\n", TextSize);
  printf("Change Ratio %d;\n", TextRatio);
  printf("Change Font %s;\n", TextFont[IdxFnt]);

  if(VerticalChart == 1) {
   defPos();
   DrillChartVertical(0);
  }
  if(VerticalChart == 0) {
   defHigh();
   DrillChartHorizontal(0);
  }

  printf("WRITE %s;\n",LbrPath);
  printf("CLOSE %s;\n",LbrPath);
  if(SymbolLayer != 44 && SymbolLayer != 45) {
   printf("DISPLAY 23 44 45 %d;\n",SymbolLayer);
  }
  else {printf("DISPLAY 23 44 45;\n");}
  printf("Grid mil 25 1 mil;\n");
  printf("USE %s\n",LbrPath);

  if (replace == 0) {
   printf("ADD 'DRILEGEND' DRILEGEND R0 (0 -1500);\n");
  }
  if (replace == 1) {
   printf("UPDATE %s;\n",LbrPath);
   printf("DISPLAY -23;\n");
   printf("Grid last;\n");
  }
 }
}


/********************DIALOG***************************/

if (EV >= 4) {

int Result = dlgDialog("DRILL LEGEND") {

 dlgTabWidget {
  dlgTabPage("Legend") {
   dlgSpacing(20);
   dlgGridLayout {
    dlgCell(0, 0) dlgSpacing(20);
    dlgCell(0, 1, 0, 5) dlgGroup("Drill Legend Settings") {
     dlgGridLayout {

      dlgCell(0, 0) dlgLabel("Field");
      dlgCell(0, 1) dlgStretch(0);
      dlgCell(0, 2) dlgLabel("Title");
      dlgCell(0, 3) dlgStretch(0);
      dlgCell(0, 4) dlgLabel("Rank");


      dlgCell(1, 0) dlgLabel(LField[0]);
      dlgCell(1, 2) dlgStringEdit(LTitle[0]);
      int SymbSel = LRank[0];
      dlgCell(1, 4) dlgComboBox(Rank, SymbSel) LRank[0] = strtol(Rank[SymbSel]);

      dlgCell(2, 0) dlgLabel(LField[1]);
      dlgCell(2, 2) dlgStringEdit(LTitle[1]);
      int ToolSel = LRank[1];
      dlgCell(2, 4) dlgComboBox(Rank, ToolSel) LRank[1] = strtol(Rank[ToolSel]);

      dlgCell(3, 0) dlgLabel(LField[2]);
      dlgCell(3, 2) dlgStringEdit(LTitle[2]);
      int MMSel = LRank[2];
      dlgCell(3, 4) dlgComboBox(Rank, MMSel) LRank[2] = strtol(Rank[MMSel]);

      dlgCell(4, 0) dlgLabel(LField[3]);
      dlgCell(4, 2) dlgStringEdit(LTitle[3]);
      int MilSel = LRank[3];
      dlgCell(4, 4) dlgComboBox(Rank, MilSel) LRank[3] = strtol(Rank[MilSel]);

      dlgCell(5, 0) dlgLabel(LField[4]);
      dlgCell(5, 2) dlgStringEdit(LTitle[4]);
      int MicSel = LRank[4];
      dlgCell(5, 4) dlgComboBox(Rank, MicSel) LRank[4] = strtol(Rank[MicSel]);

      dlgCell(6, 0) dlgLabel(LField[5]);
      dlgCell(6, 2) dlgStringEdit(LTitle[5]);
      int QtySel = LRank[5];
      dlgCell(6, 4) dlgComboBox(Rank, QtySel) LRank[5] = strtol(Rank[QtySel]);

      dlgCell(7, 0) dlgLabel(LField[6]);
      dlgCell(7, 2) dlgStringEdit(LTitle[6]);
      int TypeSel = LRank[6];
      dlgCell(7, 4) dlgComboBox(Rank, TypeSel) LRank[6] = strtol(Rank[TypeSel]);

      dlgCell(8, 0) dlgLabel(LField[7]);
      dlgCell(8, 2) dlgStringEdit(LTitle[7]);
      int ToleSel = LRank[7];
      dlgCell(8, 4) dlgComboBox(Rank, ToleSel) LRank[7] = strtol(Rank[ToleSel]);

     }
    }
    dlgCell(0, 6) dlgSpacing(20);
    dlgCell(1, 0) dlgLabel("");
    dlgCell(2, 1, 2, 3) dlgGroup("Drill Legend Orientation") {
     dlgGridLayout {
      dlgCell(0, 0) dlgRadioButton("Horizontal", VerticalChart);
      dlgCell(0, 1) dlgLabel(" ");
      dlgCell(0, 2) dlgRadioButton("Vertical", VerticalChart);
     }
    }
    dlgCell(2, 5) dlgPushButton("Help")
    int Result = dlgDialog("Drill Legend Help") {
     dlgGridLayout {
      dlgCell(0, 0) dlgLabel("\n\n\n\n\n\n\n\n\n\n\n\n\n\n\n\n\n\n\n\n\n");
      dlgCell(0, 0, 0, 2) dlgTextView(HelpLegend);
      dlgCell(1, 1) dlgSpacing(280);
      dlgCell(1, 2) dlgPushButton("+Close") dlgAccept();
     }
    };
   }
   dlgSpacing(20);
  }

  dlgTabPage("Holes") {
   string dec[] = {"0","1","2","3"};
   dlgSpacing(20);
   dlgGridLayout {
    dlgCell(0, 0) dlgSpacing(20);
    dlgCell(0, 1) dlgGroup("Non-Plated") {
     dlgRadioButton("Alternate ", SortHoles);
     dlgRadioButton("Mixed", SortHoles);
     dlgRadioButton("Last", SortHoles);
    }
    dlgCell(0, 2) dlgSpacing(10);

    dlgCell(0, 3, 0, 6) dlgGroup("Plated Status") {
     dlgGridLayout {
      dlgCell(0, 0) dlgLabel("Not Plated ");
      dlgCell(1, 0) dlgLabel("Mixed");
      dlgCell(2, 0) dlgLabel("Plated");
      dlgCell(0, 1) dlgStringEdit(PlatedStatus[0]);
      dlgCell(1, 1) dlgStringEdit(PlatedStatus[1]);
      dlgCell(2, 1) dlgStringEdit(PlatedStatus[2]);
     }
    }
    dlgCell(0, 7) dlgSpacing(20);
    dlgCell(1, 1) dlgLabel("");

    dlgCell(2, 1) dlgGroup("Unit Precision") {
     dlgGridLayout {
      dlgCell(0, 0) dlgLabel("Mils ");
      dlgCell(1, 0) dlgLabel("MM");
      dlgCell(0, 1) dlgComboBox(dec, decMIL);
      dlgCell(1, 1) dlgComboBox(dec, decMM);
     }
    }


    dlgCell(2, 3, 2, 6) dlgGroup("Holes Tolerance") {
     dlgGridLayout {
      dlgCell(0, 0) dlgLabel("Plated ");
      dlgCell(0, 1) dlgStringEdit(TolPlated);
      dlgCell(1, 0) dlgLabel("Non-Plated ");
      dlgCell(1, 1) dlgStringEdit(TolNonPlated);
     }
    }
    dlgCell(3, 1) dlgStretch(0);

    dlgCell(4, 6) dlgPushButton("Help")
     int Result = dlgDialog("Drill Legend Help") {
       dlgGridLayout {
        dlgCell(0, 0) dlgLabel("\n\n\n\n\n\n\n\n\n\n\n\n\n\n\n\n\n\n\n\n\n");
        dlgCell(0, 0, 0, 2) dlgTextView(HelpHoles);
        dlgCell(1, 1) dlgSpacing(280);
        dlgCell(1, 2) dlgPushButton("+Close") dlgAccept();
      }
     };
   }
   dlgSpacing(20);
  }


  dlgTabPage("Symbols") {
   dlgSpacing(20);
   dlgGridLayout {
    dlgCell(0, 0) dlgSpacing(20);
    dlgCell(0, 1, 0, 4) dlgGroup("Symbol Settings") {
     dlgLabel("");
     dlgGridLayout {
      dlgCell(0, 0) dlgLabel("Symbol layer  ");
      dlgCell(0, 1, 0, 2) dlgComboBox(LayerName,LayerSel) SymbolLayer = LayerNbr[LayerSel];

      dlgCell(0, 3) dlgStretch(0);
      dlgCell(1, 0) dlgLabel("");
      dlgCell(2, 0) dlgLabel("Symbol size  ");
      dlgCell(2, 1) dlgSpinBox(SymbolSize, 1, 500);
      dlgCell(2, 2) dlgLabel(" mils\t");
      dlgCell(2, 3) dlgStretch(0);
      dlgCell(3, 0) dlgLabel("");
      dlgCell(4, 0) dlgLabel("Symbol width  ");
      dlgCell(4, 1) dlgSpinBox(SymbolWidth, 0, 20);
      dlgCell(4, 2) dlgLabel(" mils");
      dlgCell(4, 3) dlgSpacing(100);
     }
     dlgLabel("");
    }
    dlgCell(0, 5) dlgSpacing(20);
    dlgCell(1, 1) dlgStretch(0);
    dlgCell(2, 4) dlgPushButton("Help")
    int Result = dlgDialog("Drill Legend Help") {
     dlgGridLayout {
      dlgCell(0, 0) dlgLabel("\n\n\n\n\n\n\n\n\n\n\n\n\n\n\n\n\n\n\n\n\n");
      dlgCell(0, 0, 0, 2) dlgTextView(HelpSymbols);
      dlgCell(1, 1) dlgSpacing(280);
      dlgCell(1, 2) dlgPushButton("+Close") dlgAccept();
     }
    };
   }

   dlgSpacing(20);
  }

  dlgTabPage("Texts") {
   dlgSpacing(20);
   dlgGridLayout {
    dlgCell(0, 0) dlgSpacing(20);
    dlgCell(0, 1, 0, 4) dlgGroup("Texts Settings") {
     dlgLabel("");
     dlgGridLayout {
      dlgCell(0, 0) dlgLabel("Text font  ");
      int TfontSel = IdxFnt;
      dlgCell(0, 1, 0, 3) dlgComboBox(TextFont, TfontSel) IdxFnt = TfontSel;
      dlgCell(0, 4) dlgLabel("\t\t        ");
      dlgCell(1, 0) dlgLabel("");
      dlgCell(2, 0) dlgLabel("Text size  ");
      dlgCell(2, 1) dlgSpinBox(TextSize, 1, 500);
      dlgCell(2, 2) dlgLabel(" mils\t    ");
      dlgCell(3, 0) dlgLabel("");
      dlgCell(4, 0) dlgLabel("Text ratio  ");
      dlgCell(4, 1) dlgSpinBox(TextRatio, 0, 20);
      dlgCell(4, 2) dlgLabel(" %");
     }
     dlgLabel("");
    }
    dlgCell(0, 5) dlgSpacing(20);
    dlgCell(1, 1) dlgStretch(0);
    dlgCell(2, 4) dlgPushButton("Help")
    int Result = dlgDialog("Drill Legend Help") {
     dlgGridLayout {
      dlgCell(0, 0) dlgLabel("\n\n\n\n\n\n\n\n\n\n\n\n\n\n\n\n\n\n\n\n\n");
      dlgCell(0, 0, 0, 2) dlgTextView(HelpTexts);
      dlgCell(1, 1) dlgSpacing(280);
      dlgCell(1, 2) dlgPushButton("+Close") dlgAccept();
     }
    };
   }
   dlgSpacing(20);
  }


  dlgTabPage("Table") {
   dlgSpacing(20);
   dlgGridLayout {
    dlgCell(0, 0) dlgSpacing(20);
    dlgCell(0, 1, 0, 4) dlgGroup("Cell Margin Factor") {
     dlgGridLayout {
      dlgCell(0, 0) dlgLabel("Horizontal ");
      dlgCell(0, 1) dlgRealEdit(WideCellFactor, 1.0, 5.0);
      dlgCell(0, 2) dlgLabel("\t\t ");
      dlgCell(0, 3) dlgStretch(0);
      dlgCell(2, 0) dlgLabel("Vertical ");
      dlgCell(2, 1) dlgRealEdit(HighCellFactor, 1.0, 5.0);
     }
    }
    dlgCell(0, 5) dlgSpacing(20);
    dlgCell(1, 1) dlgLabel(" ");
    dlgCell(2, 1, 2, 4) dlgGroup("Outline Width") {
     dlgGridLayout {
      dlgCell(0, 0) dlgLabel("Cell ");
      dlgCell(0, 1) dlgSpinBox(CellOutline, 1, 50);
      dlgCell(0, 2) dlgLabel(" mils\t\t");
      dlgCell(0, 3) dlgStretch(0);
      dlgCell(1, 0) dlgLabel("Title ");
      dlgCell(1, 1) dlgSpinBox(TitleOutline, 1, 50);
      dlgCell(1, 2) dlgLabel(" mils");
      dlgCell(2, 0) dlgLabel("Table ");
      dlgCell(2, 1) dlgSpinBox(TableOutline, 1, 50);
      dlgCell(2, 2) dlgLabel(" mils");
     }
    }

    dlgCell(3, 1) dlgStretch(0);
    dlgCell(4, 4) dlgPushButton("Help")
     int Result = dlgDialog("Drill Legend Help") {
       dlgGridLayout {
        dlgCell(0, 0) dlgLabel("\n\n\n\n\n\n\n\n\n\n\n\n\n\n\n\n\n\n\n\n\n");
        dlgCell(0, 0, 0, 2) dlgTextView(HelpTable);
        dlgCell(1, 1) dlgSpacing(280);
        dlgCell(1, 2) dlgPushButton("+Close") dlgAccept();
      }
     };
   }
   dlgSpacing(20);
  }


  dlgTabPage("Outputs") {
   dlgSpacing(20);
   dlgGridLayout {
    dlgCell(0, 0) dlgSpacing(20);
    dlgCell(0, 1, 0, 4) dlgGroup("Drill Rack File for CAM Processor") {
     dlgGridLayout {
      dlgCell(0, 0) dlgCheckBox("Generating file ", OutputDrillRack);
      dlgCell(0, 1) dlgStringEdit(DrillRackFile);
      int unit = Unit;
      dlgCell(1, 0) dlgRadioButton("Unit mm", unit) Unit = unitMM;
      dlgCell(2, 0) dlgRadioButton("Unit inch", unit) Unit = unitINCH;
     }
    }
    dlgCell(0, 5) dlgSpacing(20);



    dlgCell(2, 1, 2, 4) dlgGroup("Drill Legend User Settings") {
     dlgGridLayout {
      dlgCell(0, 0) dlgCheckBox("Save File ", OutputUserCfg);
      dlgCell(1, 0) dlgCheckBox("Load File ", InputUserCfg);
      dlgCell(0, 1) dlgSpacing(30);
      dlgCell(0, 2) dlgLabel(UserCfgFile);
     }
    }
    dlgCell(2, 5) dlgSpacing(20);
    dlgCell(3, 1) dlgStretch(0);
    dlgCell(4, 4) dlgPushButton("Help")
    int Result = dlgDialog("Drill Legend Help") {
     dlgGridLayout {
      dlgCell(0, 0) dlgLabel("\n\n\n\n\n\n\n\n\n\n\n\n\n\n\n\n\n\n\n\n\n");
      dlgCell(0, 0, 0, 2) dlgTextView(HelpOutputs);
      dlgCell(1, 1) dlgSpacing(280);
      dlgCell(1, 2) dlgPushButton("+Close") dlgAccept();
     }
    };
   }
   dlgSpacing(20);
  }
 }
 dlgHBoxLayout {
  dlgStretch(10);
  dlgPushButton("+OK") {
   dlgAccept();
   if(OutputUserCfg == 1) {OutputUserCfgFile();}
   if(OutputDrillRack == 1) {OutDrillRack();}
   TitleList();
   SortHolesMode(SortHoles);
   OutDriLegend();

   exit("; SCR '" + ScrName + "';\n");
  }

  dlgStretch(0);
  dlgPushButton("-Cancel") dlgReject();
  dlgStretch(0);
 }
};

}
else {
 string OlderVersion;
 sprintf(OlderVersion,"Sorry! Your Eagle version is %d.%d\nBut this ULP require at least 4.04\nPlease, Download the last version\nfrom: http://www.cadsoft.de",EV,ER);
 if (dlgMessageBox(OlderVersion, "&See you soon!") == 0) {}
}
