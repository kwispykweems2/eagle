#usage	"<b>Generate package CHP v1.0 15/02/06</b><br>"
	"<br>"
	"Generates packages for SMT chip resistors, capacitors and inductors. Must be run from an empty library package window and all arguments must be specified. Use parameters from the IPC land pattern calculator or the manufacturers datasheet. Pin 1 is located at the left and all parameters are specified in mm.<br>"
	"<br>"
	"Arguments:<br>"
	"<table>"
	"<tr><td>pad_x</td><td>pad width</td></tr>"
	"<tr><td>pad_y</td><td>pad length</td></tr>"
	"<tr><td>pad_space</td><td>pad spacing (center to center)</td></tr>"
	"<tr><td>keepout_x</td><td>keepout region width</td></tr>"
	"<tr><td>keepout_y</td><td>keepout region length</td></tr>"
	"<tr><td>silkscreen_x</td><td>silkscreen region width</td></tr>"
	"<tr><td>silkscreen_y</td><td>silkscreen region length</td></tr>"
	"<tr><td>component_l</td><td>component width (including pins)</td></tr>"
	"<tr><td>component_t</td><td>pin length (in contact with pad, not used)</td></tr>"
	"<tr><td>component_w</td><td>component body width</td></tr>"
	"<tr><td>component_h</td><td>component body height (not used)</td></tr>"
	"</table>"
	"<br>"
	"Example (IPC-7351A RESC2012X70N): RUN genpkg_chp RUN genpkg_chp 1.4 1.05 1.9 3.5 1.9 0 1.4 2 0.4 1.25 0.7<br>"
	"<br>"
	"Copyright 2006 Weartronics<br>"
	"http://www.weartronics.com/<br>"

if(package != 1)
	exit(EXIT_FAILURE);

if(argc != 12)
	exit(EXIT_FAILURE);

real _LINE_WIDTH = 0.127;
real _CLEARANCE = 0.254;
real _TEXT_SIZE = 1.27;
int _TEXT_RATIO = 10;

real pad_x = strtod(argv[1]);
real pad_y = strtod(argv[2]);
real pad_space = strtod(argv[3]);
real keepout_x = strtod(argv[4]);
real keepout_y = strtod(argv[5]);
real silkscreen_x = strtod(argv[6]);
real silkscreen_y = strtod(argv[7]);
real component_l = strtod(argv[8]);
real component_t = strtod(argv[9]);
real component_w = strtod(argv[10]);
real component_h = strtod(argv[11]);

string result = "";
string buffer = "";

void concat()
{
	string strings[] = {result, buffer};
	result = strjoin(strings, ' ');
}

sprintf(buffer, "GRID mm;"); concat();
sprintf(buffer, "SET WIRE_BEND 2;"); concat();
sprintf(buffer, "CHANGE FONT vector;"); concat();
sprintf(buffer, "CHANGE SIZE %f;", _TEXT_SIZE); concat();
sprintf(buffer, "CHANGE RATIO %d;", _TEXT_RATIO); concat();

sprintf(buffer, "LAYER Top;"); concat();
sprintf(buffer, "SMD %f %f -0 R90 '1' (-%f 0);", pad_x, pad_y, pad_space/2); concat();
sprintf(buffer, "SMD %f %f -0 R90 '2' (%f 0);", pad_x, pad_y, pad_space/2); concat();

sprintf(buffer, "LAYER tKeepout;"); concat();
sprintf(buffer, "WIRE 0 (-%f -%f) (-%f %f) (%f %f) (%f -%f) (-%f -%f);", keepout_x/2, keepout_y/2, keepout_x/2, keepout_y/2, keepout_x/2, keepout_y/2, keepout_x/2, keepout_y/2, keepout_x/2, keepout_y/2); concat();

sprintf(buffer, "LAYER tPlace;"); concat();
if(silkscreen_x >= 0.5)
{
	sprintf(buffer, "WIRE %f (-%f %f) (%f %f);", _LINE_WIDTH, silkscreen_x/2, silkscreen_y/2, silkscreen_x/2, silkscreen_y/2); concat();
	sprintf(buffer, "WIRE %f (-%f -%f) (%f -%f);", _LINE_WIDTH, silkscreen_x/2, silkscreen_y/2, silkscreen_x/2, silkscreen_y/2); concat();
}
else if(silkscreen_x > 0)
{
	sprintf(buffer, "WIRE %f (0 %f) (0 -%f);", _LINE_WIDTH, silkscreen_y/2, silkscreen_y/2); concat();
}

sprintf(buffer, "LAYER tDocu;"); concat();
sprintf(buffer, "WIRE %f (-%f -%f) (-%f %f) (%f %f) (%f -%f) (-%f -%f);", _LINE_WIDTH, component_l/2, component_w/2, component_l/2, component_w/2, component_l/2, component_w/2, component_l/2, component_w/2, component_l/2, component_w/2); concat();
sprintf(buffer, "RECT (-%f -%f) (-%f %f);", component_l/2, component_w/2, (component_l - component_t*2)/2, component_w/2); concat();
sprintf(buffer, "RECT (%f -%f) (%f %f);", component_l/2, component_w/2, (component_l - component_t*2)/2, component_w/2); concat();

sprintf(buffer, "LAYER tNames;"); concat();
if(silkscreen_y/2 + _LINE_WIDTH/2 + _CLEARANCE >= pad_x/2 + _CLEARANCE)
{

	sprintf(buffer, "TEXT '>NAME' (-%f %f);", pad_space/2 + pad_y/2, silkscreen_y/2 + _LINE_WIDTH/2 + _CLEARANCE); concat();
}
else
{
	sprintf(buffer, "TEXT '>NAME' (-%f %f);", pad_space/2 + pad_y/2, pad_x/2 + _CLEARANCE); concat();
}
	
sprintf(buffer, "LAYER tValues;"); concat();
if(silkscreen_y/2 + _LINE_WIDTH/2 + _CLEARANCE >= pad_x/2 + _CLEARANCE)
{
	sprintf(buffer, "TEXT '>VALUE' (-%f -%f);", pad_space/2 + pad_y/2, silkscreen_y/2 + _LINE_WIDTH/2 + _CLEARANCE + _TEXT_SIZE); concat();
}
else
{
	sprintf(buffer, "TEXT '>VALUE' (-%f -%f);", pad_space/2 + pad_y/2, pad_x/2 + _CLEARANCE + _TEXT_SIZE); concat();
}

sprintf(buffer, "WINDOW fit;"); concat();

exit(result);
